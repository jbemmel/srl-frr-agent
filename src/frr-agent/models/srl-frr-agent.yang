module srl-frr-agent {

    yang-version "1";

    namespace "urn:srl_nokia/frr";

    prefix "srl_nokia-frr";

    import srl_nokia-common {
        prefix srl_nokia-comm;
    }
    import srl_nokia-network-instance {
        prefix srl_nokia-netinst;
    }
    import srl_nokia-interfaces {
        prefix srl_nokia-if;
    }
    import srl_nokia-if-ip {
        prefix srl_nokia-if-ip;
    }
    import srl_nokia-extensions {
        prefix srl_nokia-ext;
    }

    import srl_nokia-bgp {
        prefix srl_nokia-bgp;
    }

    import srl_nokia-features { prefix srl_feat; }

    revision "2021-12-21" {
        description "Initial revision";
        reference "TBD";
    }

    typedef peer-as-spec {
      type union {
        type uint32 { range "1..4294967295"; }
        type enumeration { enum "external"; enum "internal"; }
      }
    }

    grouping frr-top {
        description "Configure FRR";

        container experimental-frr {
            presence "Configure FRR BGP";
            srl_nokia-ext:delivery-node-override true;
            must "../../type != 'srl_nokia-netinst:mac-vrf'" {
              error-message "FRR configuration is not supported on network-instance of type mac-vrf";
            }
            // must "not(../bgp)" {
            //  error-message "Either BGP or FRR can be configured for a network-instance, not both";
            // }

            leaf admin-state {
                type srl_nokia-comm:admin-state;
                default "enable";

                must ". = 'disable' or /system/gnmi-server/unix-socket/admin-state = 'enable'" {
                 error-message "This agent requires the gNMI Unix socket to be enabled";
                }

                description
                    "Administratively enable or disable the entire FRR BGP instance

                    Disable causes all BGP sessions to be taken down immediately, even if admin-state at the group or neighbor level of some of these sessions is still set as enable.";
            }

            // Allow provisioning of BGP neighbors, using the native model
            // Requires the groups too, as neighbors reference group-name
            // Needs to be at this level as opposed to 'bgp'
            uses srl_nokia-bgp:bgp-group;
            uses srl_nokia-bgp:bgp-neighbor;

            container bgp {
              presence "Configure BGP";
              leaf admin-state {
                type srl_nokia-comm:admin-state;
                default "enable";

                description
                    "Administratively enable or disable the FRR BGP daemon";
              }

              leaf port {
                type uint16;
                default 1179;
                description "TCP port for FRR bgpd to listen on, default 1179 (non-standard)";
                must ". != 179 or not(../../../bgp)" {
                   error-message "If Nokia BGP is configured, FRR BGP cannot use TCP port 179 in the same network-instance";
                }
              }

              leaf preference {
                description "The default route table preference for all FRR BGP learned routes
                    BGP import policies can override this preference value on a route by route basis.";

                type uint8;
                default 170;
              }

              leaf assign-static-ipv6 {
                description "Flag to assign static IPv6 addresses from RFC4193, if not use auto-assigned link-local";
                type boolean;
                default true; // For some reason we cannot create ipv6 link-local nexthops via NDK
              }

              leaf use-ipv6-nexthops-for-ipv4 {
                description "Flag to enable the use of IPv6 nexthops for IPv4, default enabled";
                type boolean;
                default true; // In versions before 21.11.1 bgpd crashed, but not anymore
                // must ".=false() or not(../../../bgp)" {
                //  error-message "Cannot use ipv6 nexthops for ipv4 when bgp is used";
                // }
              }

              leaf use-ipv4-link-local-range {
                description "Flag to enable the use of IPv4 link local addresses, supported starting release 21.11";
                if-feature "srl_feat:future-21-11";
                type boolean;
                default true;
              }

              leaf route-import {
                description "Selects the route import mechanism";
                type enumeration {
                  enum ndk {
                    description "Use the SRL NDK to import ipv4/v6 routes from FRR";
                  }
                  enum linux {
                    description "Use the built-in 'linux' protocol to import routes; ipv6 only and no ECMP";
                  }
                }
                default "ndk";
              }

              // TODO: Accept 'magic' routes that denote anycast rewrite rules
              leaf anycast-nexthop {
                type srl_nokia-comm:ip-address;
                description "Configure FRR to rewrite the nexthop with this anycast IP (presumably announced by BGP peers)";
              }

              container addpath {
                description "Mapping of FRR Add Path capabilities";
                leaf tx-all-paths { type boolean; default false; }
                leaf tx-bestpath-per-AS { type boolean; default false; }
                leaf disable-rx { type boolean; default false; }
              }
            }
            container eigrp {
              presence "Configure EIGRP";
              leaf admin-state {
                type srl_nokia-comm:admin-state;
                default "enable";

                description
                    "Administratively enable or disable the Enhanced Interior Gateway Routing Protocol (EIGRP) daemon";

                must ". = 'disable' or ../../autonomous-system < 65536" {
                   error-message "EIGRP only supports AS numbers between 1 and 65535";
                }
              }

              leaf create-veth-multicast-bypass {
                type boolean;
                default true;
                description "Enable multicast reception by creating a custom subinterface on e1-1";
              }
            }
            leaf autonomous-system {
                type uint32 {
                  range "1..4294967295";
                }
                mandatory "true";
                description
                    "The global AS number of the BGP instance

                    Values greater than 65535 must be entered in ASPLAIN format.";
            }

            //
            // Could add logic for this agent to subscribe to gNMI, waiting for
            // this config item. It could come from protocols/bgp/router-id
            // locally, or even from some remote config server
            //
            leaf router-id {
                //type srl_nokia-comm:dotted-quad;
                type srl_nokia-comm:ip-address;
                mandatory "true";
                description
                    "The BGP identifier used by this BGP instance in all of its OPEN messages

                    Any non-zero value is supported.";
            }

            container openfabric {
              presence "Configure OpenFabric";
              leaf name {
                type string;
                default "SRLinux";
                description "Fabric name (required, default 'SRLinux')";
              }
              leaf net {
                type string;
                default "auto";
                description "Network Entity Title (NET), e.g. '49.0000.0000.0001.00'
                             Default 'auto' uses 49.0001.<6-byte system MAC>.00";
              }
              leaf admin-state {
                type srl_nokia-comm:admin-state;
                default "enable";

                description
                    "Administratively enable or disable the FRR OpenFabric daemon";

                must ". = 'disable' or not(../../../isis)" {
                   error-message "Either Nokia ISIS or FRR OpenFabric can be configured for a network-instance, not both";
                }
              }
              leaf domain-password {
                type string;
                default "";
                description "Optional MD5 password string";
              }
              leaf fabric-tier {
                type uint8 {
                  range "0..14";
                }
                description "Optional statically configured fabric tier (0..14)";
              }
            }

            leaf oper-state {
                config false;
                // type enumeration {
                //    enum "up" {
                //        description "Operational state of FRR process is up.";
                //    }
                //    enum "down" {
                //        description "Operational state of FRR process is down.";
                //    }
                // }
                type string;
                default "down";
            }

            list peer {
             config false;
             key router-id;
             leaf router-id { type srl_nokia-comm:ip-address; }
             leaf peer-as {
              type uint32 { range "1..4294967295"; }
              description "Auto-discovered peer AS";
             }
             leaf last-updated {
               type srl_nokia-comm:date-and-time-delta;
             }
            }

            container stats {
              presence "Stats";
              srl_nokia-ext:delivery-node-override true;
              config false;

              container routes {
                leaf ipv4 { type srl_nokia-comm:zero-based-counter64; }
                leaf ipv6 { type srl_nokia-comm:zero-based-counter64; }
              }
            }
        }
    }

    augment "/srl_nokia-netinst:network-instance/srl_nokia-netinst:protocols" {
        uses frr-top;
    }

    augment "/srl_nokia-netinst:network-instance/srl_nokia-netinst:interface" { // list

      container bgp-unnumbered {
          presence "BGP unnumbered functionality";
          description "Initiate a BGP unnumbered peering session on this interface";

          must "../../srl_nokia-netinst:protocols/experimental-frr" {
            error-message "BGP unnumbered requires experimental-frr to be configured for this network-instance";
          }
          must "../type != 'srl_nokia-netinst:mac-vrf'" {
            error-message "BGP unnumbered is not supported on network-instance of type mac-vrf";
          }
          must "/srl_nokia-if:interface[srl_nokia-if:name=substring-before(../name, '.')]/srl_nokia-if:subinterface[srl_nokia-if:index=substring-after(../name, '.')]/srl_nokia-if:type != 'srl_nokia-if:bridged'" {
            error-message "BGP unnumbered interfaces cannot have type 'bridged'";
          }
          must "not(starts-with(../srl_nokia-if:name, 'mgmt') or starts-with(../srl_nokia-if:name, 'lo')
                or starts-with(../srl_nokia-if:name, 'system'))" {
            error-message "BGP unnumbered cannot be configured for this type of interface";
          }
          // For auto-discovery to work, both must be enabled
          //must "/srl_nokia-if:interface[srl_nokia-if:name=substring-before(../name, '.')]/srl_nokia-if:subinterface[srl_nokia-if:index=substring-after(../name, '.')]/srl_nokia-if-ip:ipv4" {
          //  error-message "BGP unnumbered interfaces must have ipv4 enabled";
          //}
          must "/srl_nokia-if:interface[srl_nokia-if:name=substring-before(../name, '.')]/srl_nokia-if:subinterface[srl_nokia-if:index=substring-after(../name, '.')]/srl_nokia-if-ip:ipv6" {
            error-message "BGP unnumbered interfaces must have ipv6 enabled";
          }

          leaf peer-as {
           type peer-as-spec;
           description "Expecting the given peer AS: 'external' or 'internal' for auto-discovery
                        or a number between 1..4294967295";
          }

          container status {
           srl_nokia-ext:delivery-node-override true;
           config false;

           leaf discovered-peer-as { type uint32 { range "1..4294967295"; } }
           leaf oper-state { type string; default "down"; }
           leaf router-id { type srl_nokia-comm:ip-address; }
           leaf last-updated { type srl_nokia-comm:date-and-time-delta; }
          }
       }

       container openfabric {
         presence "Openfabric interface config";
         leaf activate {
           description "Activate OpenFabric for this interface";
           type boolean;
           default false;

           must ".=false() or ../../../srl_nokia-netinst:protocols/experimental-frr" {
             error-message "OpenFabric requires experimental-frr to be configured for this network-instance";
           }
         }
       }
    }

}
