module srl-frr-agent {

    yang-version "1";

    namespace "urn:srl_nokia/frr";

    prefix "srl_nokia-frr";

    import srl_nokia-common {
        prefix srl_nokia-comm;
    }
    import srl_nokia-network-instance {
        prefix srl_nokia-netinst;
    }
    import srl_nokia-interfaces {
        prefix srl_nokia-if;
    }
    import srl_nokia-if-ip {
        prefix srl_nokia-if-ip;
    }
    import srl_nokia-extensions {
        prefix srl_nokia-ext;
    }

    revision "2021-08-03" {
        description "Initial revision";
        reference "TBD";
    }

    typedef peer-as-spec {
      type union {
        type uint32 { range "1..4294967295"; }
        type enumeration { enum "external"; enum "internal"; }
      }
    }

    grouping frr-top {
        description "Configure FRR";

        container experimental-frr {
            presence "Configure FRR BGP";
            must "../../type != 'srl_nokia-netinst:mac-vrf'" {
              error-message "FRR configuration is not supported on network-instance of type mac-vrf";
            }
            must "not(../bgp)" {
              error-message "Either BGP or FRR can be configured for a network-instance, not both";
            }

            leaf admin-state {
                type srl_nokia-comm:admin-state;
                default "enable";

                description
                    "Administratively enable or disable the entire FRR BGP instance

                    Disable causes all BGP sessions to be taken down immediately, even if admin-state at the group or neighbor level of some of these sessions is still set as enable.";
            }
            leaf autonomous-system {
                type uint32 {
                  range "1..4294967295";
                }
                mandatory "true";
                description
                    "The global AS number of the BGP instance

                    Values greater than 65535 must be entered in ASPLAIN format.";
            }
            leaf local-preference {
                type uint32;
                default 100;
                description
                    "The value of the local-preference attribute that is added to received routes from EBGP peers

                    It is also used to encode the local preference attribute for locally generated BGP routes.";
            }
            leaf router-id {
                //type srl_nokia-comm:dotted-quad;
                type srl_nokia-comm:ip-address;
                mandatory "true";
                description
                    "The BGP identifier used by this BGP instance in all of its OPEN messages

                    Any non-zero value is supported.";
            }

            leaf oper-state {
                config false;
                type enumeration {
                    enum "up" {
                        description "Operational state of FRR BGP is up.";
                    }
                    enum "down" {
                        description "Operational state of FRR BGP is down.";
                    }
                }
            }
        }
    }

    augment "/srl_nokia-netinst:network-instance/srl_nokia-netinst:protocols" {
        uses frr-top;
    }

    augment "/srl_nokia-netinst:network-instance/srl_nokia-netinst:interface" { // list

      leaf bgp-unnumbered-peer-as {
          description "Initiate a BGP unnumbered peering session on this interface,
                       expecting the given peer AS: 'external' or 'internal' for auto-discovery
                       or a number between 1..4294967295";
          type peer-as-spec;

          must "../../srl_nokia-netinst:protocols/experimental-frr" {
            error-message "BGP unnumbered requires experimental-frr to be configured for this network-instance";
          }
          must "../type != 'srl_nokia-netinst:mac-vrf'" {
            error-message "BGP unnumbered is not supported on network-instance of type mac-vrf";
          }
          must "/srl_nokia-if:interface[srl_nokia-if:name=substring-before(../name, '.')]/srl_nokia-if:subinterface[srl_nokia-if:index=substring-after(../name, '.')]/srl_nokia-if:type != 'srl_nokia-if:bridged'" {
            error-message "BGP unnumbered interfaces cannot have type 'bridged'";
          }
          must "not(starts-with(../srl_nokia-if:name, 'mgmt') or starts-with(../srl_nokia-if:name, 'lo')
                or starts-with(../srl_nokia-if:name, 'system'))" {
            error-message "BGP unnumbered cannot be configured for this type of interface";
          }
          // For the auto-provisioned IPv4 data path
          must "/srl_nokia-if:interface[srl_nokia-if:name=substring-before(../name, '.')]/srl_nokia-if:subinterface[srl_nokia-if:index=substring-after(../name, '.')]/srl_nokia-if-ip:ipv4" {
            error-message "BGP unnumbered interfaces must have ipv4 enabled";
          }
          must "/srl_nokia-if:interface[srl_nokia-if:name=substring-before(../name, '.')]/srl_nokia-if:subinterface[srl_nokia-if:index=substring-after(../name, '.')]/srl_nokia-if-ip:ipv6" {
            error-message "BGP unnumbered interfaces must have ipv6 enabled";
          }
       }
    }

    // TODO extend network-instance/interface with flags to
    // 1. Establish BGP unnumbered peering
    // 2. Export the interface IP to peers (?) or simply all connected
}
